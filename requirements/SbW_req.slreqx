# SbW_req
이 요구사항은 SbW 시스템의 안정성 향상을 위한 이중화 작업과 중재 제어에 관한 요구 사항을 정의합니다.

## REQ-SFA-001: Steering Force Actuator - Main (Functional)
사용자 입력 토크(user_torque_in)에 기반하여 적절한 실 조향 각도(real_steering_wheel_angle)를 계산해야 한다.
CAN 메시지(ID: 111)를 통해 실 조향 각도를 다른 모듈로 전달해야 한다.
최대 토크 범위를 초과하지 않도록 입력값을 제한해야 한다.

## REQ-SFA-002: Steering Force Actuator - Backup (Functional)
메인 SFA 모듈이 작동하지 않을 때 백업 역할을 수행해야 한다.
실 조향 각도(real_steering_wheel_angle2)를 계산하고 CAN 메시지(ID: 112)를 통해 전달한다.
정상 상태에서는 대기 모드로 작동하며, 비상 시 빠르게 활성화되어야 한다.

## REQ-RWA-001: Road Wheel Actuator - Main (Functional)
입력받은 타겟 조향각(target_roadwheel_angle)에 따라 도로 바퀴를 제어한다.
차량 속도(vehicle_speed)에 기반하여 복원 토크(restoring_torque)를 계산해야 한다.
CAN 메시지(ID: 222)를 통해 복원 토크 데이터를 전달한다.
BLDC 모터의 명령 신호를 정확히 생성하여 모터를 구동한다.

## REQ-RWA-002: Road Wheel Actuator - Backup (Functional)
메인 RWA 모듈이 비정상 작동 시 백업 역할을 수행해야 한다.
타겟 조향각(target_roadwheel_angle2)에 따라 복원 토크(restoring_torque2)를 계산 및 적용한다.
BLDC 모터를 제어하며, 차량 속도에 따라 적응형 복원력을 제공한다.

## REQ-MTR-001: Steering_motor (Functional)
RWA_main 또는 RWA_backup의 제어 신호에 따라 정확히 바퀴를 구동해야 한다.
차량 속도와 입력 조향각에 따라 전류 및 토크를 적응적으로 조정한다.
과부하 및 과열 조건을 모니터링하며, 비정상 조건 발생 시 경고 신호를 생성해야 한다.

## REQ-VCU-001: SBW_ VCU (Vehicle Control Unit) (Functional)
차량 속도(vehicle_speed) 데이터를 CAN 메시지(ID: 555)를 통해 다른 모듈로 전송해야 한다.
속도 데이터는 0.005초 주기로 갱신되어야 한다.
비정상 속도 입력(예: 음수값 또는 과도한 값)을 필터링하여 전달하지 않아야 한다.
